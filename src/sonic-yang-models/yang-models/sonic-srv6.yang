module sonic-srv6 {
    namespace "http://github.com/sonic-net/sonic-srv6";
    prefix srv6;
    yang-version 1.1;

	import ietf-inet-types {
		prefix inet;
	}

    import sonic-vrf {
		prefix vrf;
	}

    import sonic-port {
        prefix prt;
    }

    description
        "Segment Routing over IPv6 (SRv6) configuration for SONiC.";

    revision 2024-12-05 {
		description
			"Initial revision.";
	}

    container sonic-srv6 {

        container SRV6_MY_LOCATORS {
            description "SRv6 locator definitions partitioning the SID address space.";

            list SRV6_MY_LOCATORS_LIST {
                key "locator_name";

                leaf locator_name {
                    description "SRv6 locator name.";
                    type string;
                }

                leaf prefix {
                    description "IPv6 address prefix for this locator.";
                    type inet:ipv6-address;
                    mandatory true;
                }

                leaf block_len {
                    description "Length in bits of the SRv6 locator block portion.";
                    type uint8 {
                        range "1..128";
                    }

                    default 32;
                }

                leaf node_len {
                    description "Length in bits of the SRv6 locator node portion.";
                    type uint8 {
                        range "1..128";
                    }

                    default 16;
                }

                leaf func_len {
                    description "Length in bits of the SRv6 SID function portion.";
                    type uint8 {
                        range "0..128";
                    }

                    default 16;
                }

                leaf arg_len {
                    description "Length in bits of the SRv6 SID argument portion.";
                    type uint8 {
                        range "0..128";
                    }

                    default 0;
                }

                must 'block_len + node_len + func_len + arg_len <= 128';

                leaf vrf {
                    type union {
                        type leafref {
                            path "/vrf:sonic-vrf/vrf:VRF/vrf:VRF_LIST/vrf:name";
                        }
                        type string {
                            pattern 'default';
                        }
                    }
                    description "VRF name";

                    default "default";
                }
            }
        }

        container SRV6_MY_SIDS {
            description "Local SRv6 SID entries with endpoint behavior and decapsulation settings.";

            list SRV6_MY_SIDS_LIST {
                key "locator ip_prefix";

                leaf ip_prefix {
                    description "IPv6 prefix representing this SID.";
                    type inet:ipv6-prefix;
                }

                leaf locator {
                    description "Reference to the parent SRv6 locator.";
                    type leafref {
                        path "/srv6:sonic-srv6/srv6:SRV6_MY_LOCATORS/srv6:SRV6_MY_LOCATORS_LIST/srv6:locator_name";
                    }
                }

                leaf action {
                    description "SRv6 endpoint behavior (uN for prefix SID, uA for adjacency SID, uDT46 for decap with VRF lookup).";
                    type enumeration {
                        enum uN;
                        enum uA;
                        enum uDT46;
                    }
                }

                leaf decap_vrf {
                    type union {
                        type leafref {
                            path "/vrf:sonic-vrf/vrf:VRF/vrf:VRF_LIST/vrf:name";
                        }
                        type string {
                            pattern 'default';
                        }
                    }
                    description "VRF name used for decapsulation";

                    default "default";
                }

                leaf decap_dscp_mode {
                    description "DSCP handling mode for decapsulated packets.";
                    type enumeration {
                        enum uniform;
                        enum pipe;
                    }
                }

                leaf interface {
                    type leafref {
                        path "/prt:sonic-port/prt:PORT/prt:PORT_LIST/prt:name";
                    }
                    description "Reference of port which is used by srv6 SID";
                }
                // Constraint: interface is mandatory when action is uA
                must "not(action = 'uA') or interface" {
                    error-message "interface is mandatory when action is 'uA'";
                }

                leaf adj {
                    type inet:ipv6-address;
                    must "../action = 'uA'" {
                        error-message "adj is only applicable when action is 'uA'";
                    }
                    description "IPv6 adjacency address";
                }
            }
        }

        container SRV6_MY_SOURCE {
            description "SRv6 encapsulation source address.";

            list SRV6_MY_SOURCE_LIST {
                key "name";

                leaf name {
                    type string;
                    description "Source identifier";
                }

                leaf source-address {
                    type inet:ipv6-address;
                    description "IPv6 source address used for SRv6 encapsulation";
                }
            }
        }

    }
}
